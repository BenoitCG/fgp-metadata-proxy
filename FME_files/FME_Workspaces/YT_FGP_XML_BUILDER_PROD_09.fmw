FME workspace YT_FGP_XML_BUILDER_PROD_09.fmw

Parameters:
- ACTIVATE_GEO = Yes
- ACTIVATE_NON_GEO = Yes
- ACTIVATE_TRANSLATION = No
- CATALOGUE_READER_SELECT = No
- FORCED_PYCSW_URL =
- IN_CSV_LOOKUP_TABLES_DIR = C:\Users\FGP\Documents\GitHub\fgp-metadata-proxy\FME_files\LOOKUP_TABLES
- IN_FFS_TESTING_FILE = C:\Users\FGP\Desktop\YT_FFS_output.ffs
- IN_GMD_XML_TEMPLATE_DIR = C:\Users\FGP\Documents\GitHub\fgp-metadata-proxy\FME_files\XML_TEMPLATES
- IN_TBS_JSON_TEMPLATE_DIR = C:\Users\FGP\Documents\GitHub\fgp-metadata-proxy\FME_files\JSON_TEMPLATES
- LOCAL_SOURCE_METADATA_DELTA_FINDER = Yes
- LOCAL_WRITER = Yes
- LOG_FILE = C:\Data\PT_Harvester\YT\LOG\YT_FGP_XML_BUILDER.log
- OUT_JSON_LOCAL_DIR = C:\Data\PT_Harvester\YT\JSON_LOCAL
- OUT_XLS_NOTIFICATION_DIR = C:\Data\PT_Harvester\YT\XLS
- OUT_XML_FAILED_DIR = C:\Data\PT_Harvester\YT\XML_FAILED
- OUT_XML_LOCAL_DIR = C:\Data\PT_Harvester\YT\XML_LOCAL
- OUT_XML_PASSED_DIR = C:\Data\PT_Harvester\YT\XML_PASSED
- P-T_ABBR = YT
- PYCSW_OVERWRITE = NO
- SAMPLE_SELECT = No
- SAMPLE_SIZE = 10

Writers:
- XLSXW_1: XLSXW to $(OUT_XLS_NOTIFICATION_DIR)
- TEXTLINE_1: TEXTLINE to $(OUT_XML_PASSED_DIR)
- TEXTLINE_2: TEXTLINE to $(OUT_XML_FAILED_DIR)
- TEXTLINE_3: TEXTLINE to $(OUT_XML_LOCAL_DIR)

Creator
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> Tester_3
Tester_3
    BOOL_OP = OR
    COMPOSITE_TEST = 1
    TEST_CLAUSE = TEST $(CATALOGUE_READER_SELECT) = Yes
    TEST_MODE = TEST
    FAILED -> FeatureReader [INITIATOR] [off]
unworking_uyl (writer XLSXW_1)
    attributes: url string(200), _uuid_html string(20), _error string(200), fme_rejection_code string(20), _response_body string(200), _http_status_code string(20), _list__ string(200), _list string(200), xml string(200), td.div string(200), th string(200), _copynum string(200), _timestamp string(200)
dropped_dataset (writer XLSXW_1)
    attributes: sector string(200), contact string(200), contact_email string(200), id string(200), UNIQUE_ATT string(200), orig_name string(200), result string(200), license_title string(200), groups__.title string(200), notes string(200), resources__.format string(200), resources__.url string(200), resources__.name string(200), tags__.display_name string(200), title string(200), url string(200), nb_res number(20), data_collection_start_date string(200), date_created string(200), date_last_modified string(200), resource_update_cycle string(200), _timestamp string(200)
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: Reading from API
Note: Reads pre-generated FFS file for testing as substitute for YT_CATALOGUE_READER
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> AttributeExposer_5
AttributeExposer_5
    ATTR_LIST = id
    -> ATTRIBUTE_VALUE_TEXT_CLEANER
Note: Fetches data from the Yukon DKAN API
YT_CATALOGUE_READER
    DATA_OUTPUT -> ATTRIBUTE_VALUE_TEXT_CLEANER
    ERROR_OUTPUT -> VariableRetriever_4
VariableRetriever_4
    SCOPE = Global
    VALUE_ATTR = _timestamp
    VARNAME = _timestamp
    -> MISSING_RESULT_LIST_ATTRIBUTES (writer XLSXW_1)
Note: I was able to find the missing records manually in YT portal. We can use a lookup toable to map name to ID and read correctly missing records
MISSING_RESULT_LIST_ATTRIBUTES (writer XLSXW_1)
    attributes: _response_body string(200), _timestamp string(200)
Note: Removes whitespace from attributes
ATTRIBUTE_VALUE_TEXT_CLEANER
    -> Tester_4
Tester_7
    BOOL_OP = OR
    COMPOSITE_TEST = 1
    TEST_CLAUSE = TEST @Value(id) = 0903ec6a-d691-5b86-70cc-066d7a7007d8
    TEST_MODE = TEST

Bookmark: Sampler
Tester_4
    BOOL_OP = OR
    COMPOSITE_TEST = 1
    TEST_CLAUSE = TEST $(SAMPLE_SELECT) = Yes
    TEST_MODE = TEST
    PASSED -> Sampler_2
    FAILED -> AttributeExposer_3
Sampler_2
    RATE = $(SAMPLE_SIZE)
    SAMPLE_MODE = No
    SAMPLE_TYPE_LONG = First N Features
    SAMPLED -> AttributeExposer_3

Bookmark: Open License filtering
AttributeExposer_3
    ATTR_LIST = license_title
    -> Tester
Tester
    BOOL_OP = OR
    COMPOSITE_TEST = 1
    TEST_CLAUSE = TEST @Value(license_title) != ""
    TEST_MODE = TEST
    PASSED -> LICENSE_FILTER
    FAILED -> VariableRetriever_15
VariableRetriever_15
    SCOPE = Global
    VALUE_ATTR = _timestamp
    VARNAME = _timestamp
    -> AttributeExposer_9
AttributeExposer_9
    ATTR_LIST = url
    -> dataset_without licence (writer XLSXW_1)
dataset_without licence (writer XLSXW_1)
    attributes: id string(200), UNIQUE_ATT string(200), orig_name string(200), result string(200), license_title string(200), _timestamp string(200), url string(200)
LOOKUP_TABLES_READER_16
    CSV_ENCODING = utf-8
    CSV_PATH = $(IN_CSV_LOOKUP_TABLES_DIR)
    FEATURE_TYPE = License_YT
    PT = YT
    -> LICENSE_FILTER [LOOKUP_TABLE_INPUT]
LICENSE_FILTER
    LICENSE_ATT = @Value(license_title)
    LICENSE_FILTER_PASSED -> YT_DATA_READER
    UNKNOWN_LICENSE -> VariableRetriever_14
YT_DATA_READER
    Unworking_url -> VariableRetriever_5
    -> URL_HTTPS_MAKER [UUIDGenerator_Input]
    DroppedDatasets -> VariableRetriever_3
VariableRetriever_3
    SCOPE = Global
    VALUE_ATTR = _timestamp
    VARNAME = _timestamp
    -> dropped_dataset (writer XLSXW_1)
VariableRetriever_14
    SCOPE = Global
    VALUE_ATTR = _timestamp
    VARNAME = _timestamp
    -> AttributeExposer_8
AttributeExposer_8
    ATTR_LIST = url
    -> unknown_license (writer XLSXW_1)
unknown_license (writer XLSXW_1)
    attributes: license_id string(200), id string(200), UNIQUE_ATT string(200), orig_name string(200), result string(200), license_title string(200), _timestamp string(200), url string(200)

Bookmark: Formatting dates, missing attributes and contacts
Note: Making HTTPS url to avoid issues
URL_HTTPS_MAKER
VariableRetriever_5
    SCOPE = Global
    VALUE_ATTR = _timestamp
    VARNAME = _timestamp
    -> unworking_uyl (writer XLSXW_1)
Creator_3
    GEOMTYPE = Geometry Object
    NUM = 1
    CREATED -> FeatureReader_2 [INITIATOR]
FeatureReader_2
    ATTR_ACCUM_MODE = Only Use Result
    COMBINE_GEOM = Use Result
    DATASET = C:\Users\FGP\Downloads\temp22.ffs
    FFS_USE_SEARCH_ENVELOPE = NO
    FORMAT = FFS
    INTERACT = <No Spatial Filter>
    OUTPUT_FEATURES_DISPLAY = Schema and Data Features
    <OTHER> -> EMPTY_FORMAT_MAPPER [DATA_INPUT]
EMPTY_FORMAT_MAPPER
    DATA_OUTPUT -> YT_DATE_FORMATTER
Note: Sets date values to iso yyyy-mm-dd format
YT_DATE_FORMATTER
    -> DEFAULT_ATTRIBUTE_MAPPER
Note: Reading Default_YT
LOOKUP_TABLES_READER_5
    CSV_ENCODING = utf-8
    CSV_PATH = $(IN_CSV_LOOKUP_TABLES_DIR)
    FEATURE_TYPE = Default_YT
    PT = YT
    -> DEFAULT_ATTRIBUTE_MAPPER [LOOKUP_TABLE_INPUT]
DEFAULT_ATTRIBUTE_MAPPER
    -> YT_CONTACTS_MERGER
YT_CONTACTS_MERGER
    -> YT_MISSING_ATTRIBUTE_MANAGER
YT_MISSING_ATTRIBUTE_MANAGER
    -> YT_MISSING_ATTRIBUTE_MANAGER_OUTPUT
    -> AttributeExposer_6
YT_MISSING_ATTRIBUTE_MANAGER_OUTPUT: Inspector

Bookmark: Adding weblink
AttributeExposer_6
    ATTR_LIST = url
    -> FeatureMerger [REQUESTOR]
LOOKUP_TABLES_READER_6
    CSV_ENCODING = utf-8
    CSV_PATH = $(IN_CSV_LOOKUP_TABLES_DIR)
    FEATURE_TYPE = GeoportalWeblink_YT
    PT = YT
    -> GEOPORTAL_WEBLINK_ADDER [LOOKUP_TABLE_INPUT]
Note: Concatenates a base url with "orig_name" attribute to create an additional transfer option
GEOPORTAL_WEBLINK_ADDER
    WEBLINK_WILDCARD = @Value(url)
    -> FeatureMerger [REQUESTOR]

Bookmark: Transfert des mots clés de recheche pour l'assingation par tags
Note: Reading geokeyword_url
LOOKUP_TABLES_READER_15
    CSV_ENCODING = utf-8
    CSV_PATH = $(IN_CSV_LOOKUP_TABLES_DIR)
    FEATURE_TYPE = geokeyword_url
    PT = YT
    -> AttributeExposer_2
AttributeExposer_2
    ATTR_LIST = keyword
    -> ListBuilder
ListBuilder
    LIST_ATTRS_TO_INCLUDE = keyword
    LIST_NAME = _list
    -> ListConcatenator
ListConcatenator
    DROP_EMPTY_PARTS = No
    LIST_ATTR = _list{}.keyword
    SEP = |
    VAL_ATTR = _url_keyword
    -> FeatureMerger [SUPPLIER]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeCreator_4
    UNMERGED_REQUESTOR -> Terminator_2
    <REJECTED> -> Terminator_2

Bookmark: Asssingation du type spatial au ressources en se basant sur la description au lieu du format
AttributeCreator_4
    ATTR_TABLE = SET_TO _ordre = 2
    -> ListElementCounter_2
ListElementCounter_2
    CNT_ATTR = _nb_res
    LIST_NAME = resources{}
    -> AttributeExposer_10
AttributeExposer_10
    ATTR_LIST = resources{}.description
    -> Sorter
Note: Le champ resrouces{}.description du Yukon contient beaucoup d'information sur le contenu du jeu de données.
AttributeCreator_5
    ATTR_TABLE = SET_TO _ordre = 1
    -> AttributeExposer_7
AttributeExposer_7
    ATTR_LIST = format,spatial_type,fgp_publish
    -> Tester_8
Tester_8
    BOOL_OP = OR
    COMPOSITE_TEST = 1
    TEST_CLAUSE = TEST @Value(spatial_type) != ""
    TEST_MODE = TEST
    PASSED -> DuplicateFilter
DuplicateFilter
    INPUT_ORDERED_CHOICE = No
    KEYATTR = format
    UNIQUE -> Sorter
Sorter
    SORT_PARM = _ordre NUMERIC ASCENDING
    SORTED -> PythonCaller_2
PythonCaller_2
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.dict_format={}
              pass
          def input(self,feature):
              if feature.getAttribute('_ordre')==1:
                  self.dict_format[feature.getAttribute('format')]={'st':feature.getAttribute('spatial_type'),'fgp_publish':feature.getAttribute('fgp_publish')}
              else:
                  #Parcourrir toutes les ressources et si la description contient un format, on assigne le type de représenation spatiale si cette dernière n'est pas définie
                  for i in range(int(feature.getAttribute('_nb_res'))):
                      #uniquement si le spatial type de la ressource n'est pas défini
                      if not feature.getAttribute('resources{%i}.spatial_type'%(i)):

                          #uniquement si la description existe
                          if feature.getAttribute('resources{%i}.description'%(i)):

                              #Parcourrir le dictionnaire pour voir si on retrouve la clef dans la descritpion
                              #Exemple: Downloadable zip files in the following formats:.fgdb, .kmz, .shp

                              for elem in self.dict_format.keys():
                                  if elem.lower() in feature.getAttribute('resources{%i}.description'%(i)).lower():
                                      feature.setAttribute('resources{%i}.spatial_type'%(i),self.dict_format[elem]['st'])
                                      feature.setAttribute('resources{%i}.fgp_publish'%(i),self.dict_format[elem]['fgp_publish'])
                                      print(elem.lower)
                                      print(self.dict_format[elem])
                                      break


                  self.pyoutput(feature)
          def close(self):
              pass
    PYTHONSYMBOL = FeatureProcessor
    -> GEOSPATIAL_DATA_VALIDATOR

Bookmark: Geospatial/non-geospatial data filtering
Terminator_2
    MESSAGE = Translation Terminated
Note: Reading GeospatialValidation
LOOKUP_TABLES_READER
    CSV_ENCODING = utf-8
    CSV_PATH = $(IN_CSV_LOOKUP_TABLES_DIR)
    FEATURE_TYPE = GeospatialValidation
    PT = YT
    -> GEOSPATIAL_DATA_VALIDATOR [LOOKUP_TABLE_INPUT]
    -> AttributeCreator_5
Note: Second geospatial data validator using different filtering criteria
GEOSPATIAL_DATA_VALIDATOR
    KEYWORD_SEARCH = @Value(_url_keyword)
    LIST_SEARCH_ATTRIBUTE = resources{}.url
    GEOSPATIAL -> SPATIAL_TYPE_MAPPER [DATA_INPUT]
    NON-GEOSPATIAL -> MANUAL_GEOSPATIAL_SETTER [DATA_INPUT]
    UNKNOWN_FORMAT -> VariableRetriever_11
VariableRetriever_11
    SCOPE = Global
    VALUE_ATTR = _timestamp
    VARNAME = _timestamp
    -> GEOSPATIAL_FORMAT_NOT_MAPPED (writer XLSXW_1)
GEOSPATIAL_FORMAT_NOT_MAPPED (writer XLSXW_1)
    attributes: id string(200), format string(200), _timestamp string(200)
Note: Reading UnmappedGeoData_YT
LOOKUP_TABLES_READER_2
    CSV_ENCODING = utf-8
    CSV_PATH = $(IN_CSV_LOOKUP_TABLES_DIR)
    FEATURE_TYPE = UnmappedGeodata_YT
    PT = YT
    -> MANUAL_GEOSPATIAL_SETTER [LOOKUP_TABLE_INPUT]
Note: Additional filtering step required for YT data. Items identified as NON-GEOSPATIAL in GEOSPATIAL_DATA_VALIDATOR were analyzed manually and a lookup table was created to identify non-filtered geo data and create the spatial_representation_type
MANUAL_GEOSPATIAL_SETTER
    GEOSPATIAL -> Tester_6
    NON-GEOSPATIAL -> Tester_2
    UNMAPPED_DATA -> VariableRetriever_13
VariableRetriever_13
    SCOPE = Global
    VALUE_ATTR = _timestamp
    VARNAME = _timestamp
    -> UNMAPPED_GEODATA_YT (writer XLSXW_1)
UNMAPPED_GEODATA_YT (writer XLSXW_1)
    attributes: id string(200), url string(200), notes string(200), title string(200), _timestamp string(200)
Note: Select Non-Geo
Tester_2
    BOOL_OP = OR
    COMPOSITE_TEST = 1
    TEST_CLAUSE = TEST $(ACTIVATE_NON_GEO) = Yes
    TEST_MODE = TEST
    PASSED -> Junction_2
Note: Reading UUID_Spatial_YT
LOOKUP_TABLES_READER_3
    CSV_ENCODING = utf-8
    CSV_PATH = $(IN_CSV_LOOKUP_TABLES_DIR)
    FEATURE_TYPE = UUID_Spatial_YT
    PT = YT
    -> SPATIAL_TYPE_MAPPER [LOOKUP_TABLE_INPUT]
SPATIAL_TYPE_MAPPER
    DATA_OUTPUT_FAILED -> VariableRetriever_12
    DATA_OUTPUT_PASSED -> Tester_6
VariableRetriever_12
    SCOPE = Global
    VALUE_ATTR = _timestamp
    VARNAME = _timestamp
    -> SPATIAL_TYPE_NOT_MAPPED (writer XLSXW_1)
SPATIAL_TYPE_NOT_MAPPED (writer XLSXW_1)
    attributes: id string(200), url string(200), notes string(200), title string(200), _timestamp string(200)
Note: Select Geo
Tester_6
    BOOL_OP = OR
    COMPOSITE_TEST = 1
    TEST_CLAUSE = TEST $(ACTIVATE_GEO) = Yes
    TEST_MODE = TEST
    PASSED -> FORMAT_VALIDATOR

Bookmark: Nongeospatial Processing
Note: NON-GEOSPATIAL OUTPUT
Junction_2

Bookmark: Attribute Validation
Note: Verfication if URL is valid WMS call for WMS formats
FORMAT_VALIDATOR
    -> EMAIL_FORMAT_TESTER
EMAIL_FORMAT_TESTER
    DEFAULT_CONTACT_EMAIL = @Value(default_contact_email)
    -> METADATA_VALUE_MAPPER [DATA_INPUT]

Bookmark: Attribute value mapper
Note: Reading Role
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
LOOKUP_TABLES_READER_7
    CSV_ENCODING = utf-8
    CSV_PATH = $(IN_CSV_LOOKUP_TABLES_DIR)
    FEATURE_TYPE = role
    PT = YT
    -> METADATA_VALUE_MAPPER [LOOKUP_TABLE_INPUT]
Note: Maps contacts{}.role to HNAP standards
METADATA_VALUE_MAPPER
    ATT_TO_MAP = contacts{}.role
    CODE_REFRESH = YES
    ENGLISH_REFRESH = YES
    ERROR_NOT_MAPPED = YES
    FRENCH_REFRESH = YES
    -> METADATA_VALUE_MAPPER_2 [DATA_INPUT]
Note: Reading SpatialRepresentation
LOOKUP_TABLES_READER_8
    CSV_ENCODING = utf-8
    CSV_PATH = $(IN_CSV_LOOKUP_TABLES_DIR)
    FEATURE_TYPE = SpatialRepresentation
    PT = YT
    -> METADATA_VALUE_MAPPER_2 [LOOKUP_TABLE_INPUT]
Note: Maps spatial_representation_type to HNAP standards
METADATA_VALUE_MAPPER_2
    ATT_TO_MAP = spatial_representation_type
    CODE_REFRESH = YES
    ENGLISH_REFRESH = YES
    ERROR_NOT_MAPPED = YES
    FRENCH_REFRESH = YES
    -> METADATA_VALUE_MAPPER_3 [DATA_INPUT]
Note: Reading Progress
LOOKUP_TABLES_READER_9
    CSV_ENCODING = utf-8
    CSV_PATH = $(IN_CSV_LOOKUP_TABLES_DIR)
    FEATURE_TYPE = Progress
    PT = YT
    -> METADATA_VALUE_MAPPER_3 [LOOKUP_TABLE_INPUT]
Note: Maps progress_code to HNAP standards
METADATA_VALUE_MAPPER_3
    ATT_TO_MAP = progress_code
    CODE_REFRESH = YES
    ENGLISH_REFRESH = YES
    ERROR_NOT_MAPPED = YES
    FRENCH_REFRESH = YES
    -> METADATA_VALUE_MAPPER_4 [DATA_INPUT]
Note: Reading SpatialRef
LOOKUP_TABLES_READER_10
    CSV_ENCODING = utf-8
    CSV_PATH = $(IN_CSV_LOOKUP_TABLES_DIR)
    FEATURE_TYPE = SpatialRef
    PT = YT
    -> METADATA_VALUE_MAPPER_4 [LOOKUP_TABLE_INPUT]
Note: Maps spatailref_projection_name to HNAP standards
METADATA_VALUE_MAPPER_4
    ATT_TO_MAP = spatialref_projection_name
    CODE_REFRESH = NO
    ENGLISH_REFRESH = YES
    ERROR_NOT_MAPPED = YES
    FRENCH_REFRESH = NO
    -> METADATA_VALUE_MAPPER_5 [DATA_INPUT]
Note: Reading Update
LOOKUP_TABLES_READER_11
    CSV_ENCODING = utf-8
    CSV_PATH = $(IN_CSV_LOOKUP_TABLES_DIR)
    FEATURE_TYPE = Update
    PT = YT
    -> METADATA_VALUE_MAPPER_5 [LOOKUP_TABLE_INPUT]
Note: Maps resource_update_cycle to HNAP standards
METADATA_VALUE_MAPPER_5
    ATT_TO_MAP = resource_update_cycle
    CODE_REFRESH = YES
    ENGLISH_REFRESH = YES
    ERROR_NOT_MAPPED = YES
    FRENCH_REFRESH = YES
    -> METADATA_VALUE_MAPPER_6 [DATA_INPUT]
Note: Reading Email
LOOKUP_TABLES_READER_13
    CSV_ENCODING = utf-8
    CSV_PATH = $(IN_CSV_LOOKUP_TABLES_DIR)
    FEATURE_TYPE = Email
    PT = YT
    -> METADATA_VALUE_MAPPER_6 [LOOKUP_TABLE_INPUT]
Note: Maps contacts{}.email to HNAP standards
METADATA_VALUE_MAPPER_6
    ATT_TO_MAP = contacts{}.email
    CODE_REFRESH = NO
    ENGLISH_REFRESH = YES
    ERROR_NOT_MAPPED = NO
    FRENCH_REFRESH = NO
    -> METADATA_FORMAT_MAPPER [DATA_INPUT]
Note: Reading Format
LOOKUP_TABLES_READER_12
    CSV_ENCODING = utf-8
    CSV_PATH = $(IN_CSV_LOOKUP_TABLES_DIR)
    FEATURE_TYPE = Format
    PT = YT
    -> METADATA_FORMAT_MAPPER [LOOKUP_TABLE_INPUT]
Note: Maps resources{}.format to HNAP standards
METADATA_FORMAT_MAPPER
    ATT_TO_MAP = resources{}.format
    ERROR_NOT_MAPPED = YES
    REAL_VALUE_REFRESH = YES
    RES_TYPE_EN_REFRESH = YES
    RES_TYPE_FR_REFRESH = YES
    -> METADATA_VALUE_MAPPER_ERROR_MANAGER

Bookmark: Mapping error list creator
Note: Writes mapping errors to Excel file
METADATA_VALUE_MAPPER_ERROR_MANAGER
    ERROR_OUTPUT -> VariableRetriever_7
    DATA_OUTPUT -> ListElementCounter
VariableRetriever_7
    SCOPE = Global
    VALUE_ATTR = _timestamp
    VARNAME = _timestamp
    -> METADATA_MAPPING_ERRORS (writer XLSXW_1)
METADATA_MAPPING_ERRORS (writer XLSXW_1)
    attributes: id string(200), error string(200), _element_index string(200), _timestamp string(200)

Bookmark: Adjusting ESRI REST services
Note: Some ESRI REST services set by Yukon are not ESRI REST but web App. / Reset format ESRI REST to Web App to avoid issues with the RCS
ListElementCounter
    CNT_ATTR = _nb_res
    LIST_NAME = resources{}
    -> PythonCaller
PythonCaller
    PYTHONSOURCE:
      import fme
      import fmeobjects
      # Template Function interface:
      # When using this function, make sure its name is set as the value of
      # the 'Class or Function to Process Features' transformer parameter
      def processFeature(feature):
          for i in range(int(feature.getAttribute('_nb_res'))):
              if feature.getAttribute('resources{%i}.format'%(i))=='ESRI REST':
                  if r'https://yukon.maps.arcgis.com/apps' in feature.getAttribute('resources{%i}.url'%(i)):
                      feature.setAttribute('resources{%i}.format'%(i),'Web App')
    PYTHONSYMBOL = processFeature
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> MORE_INFO_MANAGER
Note: Tests the more_info{}.link list for valid attribute values and filters them out where missing
MORE_INFO_MANAGER
    -> REMOVE_BROKEN_URL_WMS_ESRI_REST

Bookmark: Data cleanup. Dropping broken web services
Note: Tests WMS/ESRI_REST resource URL's and removes them where broken
REMOVE_BROKEN_URL_WMS_ESRI_REST
    -> WMS_REST_LANGUAGE_FORMATTER
    FAULTY_URL_OUTPUT -> VariableRetriever_8
VariableRetriever_8
    SCOPE = Global
    VALUE_ATTR = _timestamp
    VARNAME = _timestamp
    -> MAP_SERVICE_URL_ERROR (writer XLSXW_1)
MAP_SERVICE_URL_ERROR (writer XLSXW_1)
    attributes: id string(200), format string(200), url string(200), _url_failure_message string(200), _timestamp string(200)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> GMD_SECTION_DATA_EXTRACTION

Bookmark: List and duplicate cleanup
Note: Creates lists and removes duplicates for GMD_Section
GMD_SECTION_DATA_EXTRACTION
    -> PYCSW_URL_MAPPER

Bookmark: Configuring publishing info
Note: Reading PyCSW_config
LOOKUP_TABLES_READER_4
    CSV_ENCODING = utf-8
    CSV_PATH = $(IN_CSV_LOOKUP_TABLES_DIR)
    FEATURE_TYPE = PyCSW_config
    PT = YT
    -> PYCSW_URL_MAPPER [PYCSW_CONFIG]
PYCSW_URL_MAPPER
    FORCED_PYCSW_URL = $(FORCED_PYCSW_URL)
    PROVIDER = $(P-T_ABBR)
    -> AttributeExposer_4
AttributeExposer_4
    ATTR_LIST = search_criteria_pycsw
    -> METADATA_DELTA_FINDER
METADATA_DELTA_FINDER
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = date_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    -> AttributeExposer
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester_5
    Update -> AWS_TRANSLATE
    Insert -> AWS_TRANSLATE
    Delete -> AttributeKeeper
Terminator
    MESSAGE = ERROR: Unknown _event value from Metadata_Delta
Note: Selects items with no change for publishing, overwriting all existing data
Tester_5
    BOOL_OP = OR
    COMPOSITE_TEST = 1
    TEST_CLAUSE = TEST $(PYCSW_OVERWRITE) = YES
    TEST_MODE = TEST
    PASSED -> AttributeCreator
    FAILED -> StatisticsCalculator
Note: Reset to update
AttributeCreator
    ATTR_TABLE = SET_TO PyCSW_Transaction = Update
    -> AWS_TRANSLATE
Note: Retains ID for list of deleted items
AttributeKeeper
    KEEP_ATTRS = id
    -> VariableRetriever_9
VariableRetriever_9
    SCOPE = Global
    VALUE_ATTR = _timestamp
    VARNAME = _timestamp
    -> DELETED_RECORDS (writer XLSXW_1)
DELETED_RECORDS (writer XLSXW_1)
    attributes: id string(200), _timestamp string(200)
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: Language Translation
Note: Translates specific items from English to French
AWS_TRANSLATE
    ACTIVATE_TRANSLATION = $(ACTIVATE_TRANSLATION)
    ATTR_2_Translate = notes,title
    ATTR_LIST_2_Translate = tags{}.display_name,resources{}.name
    MODE = English-->French
    -> XML_PUBLISHER
    TRANSLATION_PROBLEM -> VariableRetriever_10
VariableRetriever_10
    SCOPE = Global
    VALUE_ATTR = _timestamp
    VARNAME = _timestamp
    -> TRANSLATION_PROBLEMS (writer XLSXW_1)
TRANSLATION_PROBLEMS (writer XLSXW_1)
    attributes: _iteration string(200), _aws_activation string(200), _mode string(200), _attr2translate string(200), _attrlist2translate string(200), PyCSW_Transaction string(200), _hash_prov string(200), _type string(200), RESOURCES_FORMAT_ATT string(200), csw_url string(200), _ordre string(200), iso_topic__ string(200), iso_topic__.topic_value string(200), projectionList__.codespace string(200), projectionList__.projection_name string(200), projectionList__.version string(200), tags__.display_name string(200), name string(200), id string(200), _element_count_res number(20), _error string(200), _response_body string(200), _http_status_code string(20), data_collection_start_date string(200), assignation string(200), date_created string(200), date_last_modified string(200), date_published string(200), orig_name string(200), default_contact_email string(200),
      role string(200), default_contact_role string(200), contact_role string(200), xml_contact_role string(200), east_bound_longitude string(200), progress_code string(200), resource_update_cycle string(200), spatialref_projection_name string(200), spatialref_projection_system string(200), spatialref_projection_system_version string(200), contact_email string(200), xml_contact_email string(200), contact string(200), xml_contact string(200), north_bound_latitude string(200), south_bound_latitude string(200), west_bound_longitude string(200), display_name string(200), _list__.keyword string(200), _url_keyword string(20), _nb_res number(20), spatial_type string(200), notes string(200), title string(200), orig_id string(200), data_collection_end_date string(200), resources string(200), description string(200), spatial_representation_type string(200), contacts__.name string(200),
      contacts__.role string(200), contacts__.email string(200), mapping_errors__.error string(200), _element_count number(20), more_info__.protocol string(200), more_info__.id string(200), more_info__.link string(200), more_info__._element_index string(200), default_distribution_format_version string(200), title_fr string(200), _list_index_OGC_WMS string(200), _list_index_esrirest string(200), nb_OGCWMScount string(200), nb_OGCWMSvalue string(200), nb_esri_restcount string(200), nb_esri_restvalue string(200), resources__.protocol string(200), projectionList__.protocol string(200), distributionList__.protocol string(200), resources__.xlink_role string(200), projectionList__.xlink_role string(200), distributionList__.xlink_role string(200), resources__.orig_id string(200), projectionList__.orig_id string(200), distributionList__.orig_id string(200), resources__.data_collection_end_date string(200), projectionList__.data_collection_end_date string(200), distributionList__.data_collection_end_date string(200), resources__.data_collection_start_date string(200), projectionList__.data_collection_start_date string(200),
      distributionList__.data_collection_start_date string(200), resources__.format string(200), projectionList__.format string(200), distributionList__.format string(200), resources__.name string(200), projectionList__.name string(200), distributionList__.name string(200), resources__.resource_update_cycle string(200), projectionList__.resource_update_cycle string(200), distributionList__.resource_update_cycle string(200), resources__.url string(200), projectionList__.url string(200), distributionList__.url string(200), resources__.resources string(200), projectionList__.resources string(200), distributionList__.resources string(200), resources__.description string(200), projectionList__.description string(200), distributionList__.description string(200), resources__.notes string(200), projectionList__.notes string(200), distributionList__.notes string(200), resources__.title string(200), projectionList__.title string(200), distributionList__.title string(200), resources__.spatial_type string(200), projectionList__.spatial_type string(200), distributionList__.spatial_type string(200), resources__.name_fr string(200), projectionList__.name_fr string(200),
      distributionList__.name_fr string(200), resources__.id string(200), projectionList__.id string(200), distributionList__.id string(200), resources__.language_a string(200), projectionList__.language_a string(200), distributionList__.language_a string(200), resources__.language_b string(200), projectionList__.language_b string(200), distributionList__.language_b string(200), resources__.locale_a string(200), projectionList__.locale_a string(200), distributionList__.locale_a string(200), resources__.locale_b string(200), projectionList__.locale_b string(200), distributionList__.locale_b string(200), resources__.service_a string(200), projectionList__.service_a string(200), distributionList__.service_a string(200), resources__.service_b string(200), projectionList__.service_b string(200), distributionList__.service_b string(200), _histogram__.count string(200), _histogram__.value string(200), resources__.projection_name string(200), distributionList__.projection_name string(200), resources__.resource_update_cycle_code string(200), projectionList__.resource_update_cycle_code string(200), distributionList__.resource_update_cycle_code string(200), resources__.resource_update_cycle_fr string(200),
      projectionList__.resource_update_cycle_fr string(200), distributionList__.resource_update_cycle_fr string(200), updateList__.resource_update_cycle string(200), updateList__.resource_update_cycle_code string(200), updateList__.resource_update_cycle_fr string(200), more_info_0_.link string(200), search_criteria_pycsw string(200), _global_hashkey string(200), _hash_pycsw string(200), csw_version string(200), csw_schema string(200), csw_typenames string(200), csw_filter string(200), result.file_id string(200), csw_search_criteria string(200), MD_Metadata.MD_Metadata string(200), _OpenMapsFilter string(200), result.results string(200), _list_name string(200), MD_Metadata.fileIdentifier.CharacterString string(200), MD_Metadata.path_windows string(200), MD_Metadata.path_extension string(200), path_windows string(200), path_extension string(200), AWScopy_PyCSW_Transaction string(200), AWScopy__hash_prov string(200), AWScopy__type string(200), AWScopy_RESOURCES_FORMAT_ATT string(200), AWScopy_csw_url string(200), AWScopy__ordre string(200),
      AWScopy_iso_topic__ string(200), AWScopy_iso_topic__.topic_value string(200), AWScopy_projectionList__.codespace string(200), AWScopy_projectionList__.projection_name string(200), AWScopy_projectionList__.version string(200), AWScopy_tags__.display_name string(200), AWScopy_name string(200), AWScopy_id string(200), AWScopy__element_count_res number(20), AWScopy__error string(200), AWScopy__response_body string(200), AWScopy__http_status_code string(20), AWScopy_data_collection_start_date string(200), AWScopy_assignation string(200), AWScopy_date_created string(200), AWScopy_date_last_modified string(200), AWScopy_date_published string(200), AWScopy_orig_name string(200), AWScopy_default_contact_email string(200), AWScopy_role string(200), AWScopy_default_contact_role string(200), AWScopy_contact_role string(200), AWScopy_xml_contact_role string(200), AWScopy_east_bound_longitude string(200), AWScopy_progress_code string(200), AWScopy_resource_update_cycle string(200), AWScopy_spatialref_projection_name string(200), AWScopy_spatialref_projection_system string(200), AWScopy_spatialref_projection_system_version string(200), AWScopy_contact_email string(200),
      AWScopy_xml_contact_email string(200), AWScopy_contact string(200), AWScopy_xml_contact string(200), AWScopy_north_bound_latitude string(200), AWScopy_south_bound_latitude string(200), AWScopy_west_bound_longitude string(200), AWScopy_display_name string(200), AWScopy__list__.keyword string(200), AWScopy__url_keyword string(20), AWScopy__nb_res number(20), AWScopy_spatial_type string(200), AWScopy_notes string(200), AWScopy_title string(200), AWScopy_orig_id string(200), AWScopy_data_collection_end_date string(200), AWScopy_resources string(200), AWScopy_description string(200), AWScopy_spatial_representation_type string(200), AWScopy_contacts__.name string(200), AWScopy_contacts__.role string(200), AWScopy_contacts__.email string(200), AWScopy_mapping_errors__.error string(200), AWScopy__element_count number(20), AWScopy_more_info__.protocol string(200), AWScopy_more_info__.id string(200), AWScopy_more_info__.link string(200), AWScopy_more_info__._element_index string(200), AWScopy_default_distribution_format_version string(200), AWScopy_title_fr string(200), AWScopy__list_index_OGC_WMS string(200),
      AWScopy__list_index_esrirest string(200), AWScopy_nb_OGCWMScount string(200), AWScopy_nb_OGCWMSvalue string(200), fme_rejection_code string(20), AWScopy_nb_esri_restcount string(200), AWScopy_nb_esri_restvalue string(200), AWScopy_resources__.protocol string(200), AWScopy_projectionList__.protocol string(200), AWScopy_distributionList__.protocol string(200), AWScopy_resources__.xlink_role string(200), AWScopy_projectionList__.xlink_role string(200), AWScopy_distributionList__.xlink_role string(200), AWScopy_resources__.orig_id string(200), AWScopy_projectionList__.orig_id string(200), AWScopy_distributionList__.orig_id string(200), AWScopy_resources__.data_collection_end_date string(200), AWScopy_projectionList__.data_collection_end_date string(200), AWScopy_distributionList__.data_collection_end_date string(200), AWScopy_resources__.data_collection_start_date string(200), AWScopy_projectionList__.data_collection_start_date string(200), AWScopy_distributionList__.data_collection_start_date string(200), AWScopy_resources__.format string(200), AWScopy_projectionList__.format string(200), AWScopy_distributionList__.format string(200), AWScopy_resources__.name string(200), AWScopy_projectionList__.name string(200), AWScopy_distributionList__.name string(200), AWScopy_resources__.resource_update_cycle string(200), AWScopy_projectionList__.resource_update_cycle string(200), AWScopy_distributionList__.resource_update_cycle string(200),
      AWScopy_resources__.url string(200), AWScopy_projectionList__.url string(200), AWScopy_distributionList__.url string(200), AWScopy_resources__.resources string(200), AWScopy_projectionList__.resources string(200), AWScopy_distributionList__.resources string(200), AWScopy_resources__.description string(200), AWScopy_projectionList__.description string(200), AWScopy_distributionList__.description string(200), AWScopy_resources__.notes string(200), AWScopy_projectionList__.notes string(200), AWScopy_distributionList__.notes string(200), AWScopy_resources__.title string(200), AWScopy_projectionList__.title string(200), AWScopy_distributionList__.title string(200), AWScopy_resources__.spatial_type string(200), AWScopy_projectionList__.spatial_type string(200), AWScopy_distributionList__.spatial_type string(200), AWScopy_resources__.name_fr string(200), AWScopy_projectionList__.name_fr string(200), AWScopy_distributionList__.name_fr string(200), AWScopy_resources__.id string(200), AWScopy_projectionList__.id string(200), AWScopy_distributionList__.id string(200), AWScopy_resources__.language_a string(200), AWScopy_projectionList__.language_a string(200), AWScopy_distributionList__.language_a string(200), AWScopy_resources__.language_b string(200), AWScopy_projectionList__.language_b string(200), AWScopy_distributionList__.language_b string(200),
      AWScopy_resources__.locale_a string(200), AWScopy_projectionList__.locale_a string(200), AWScopy_distributionList__.locale_a string(200), AWScopy_resources__.locale_b string(200), AWScopy_projectionList__.locale_b string(200), AWScopy_distributionList__.locale_b string(200), AWScopy_resources__.service_a string(200), AWScopy_projectionList__.service_a string(200), AWScopy_distributionList__.service_a string(200), AWScopy_resources__.service_b string(200), AWScopy_projectionList__.service_b string(200), AWScopy_distributionList__.service_b string(200), AWScopy__histogram__.count string(200), AWScopy__histogram__.value string(200), AWScopy_resources__.projection_name string(200), AWScopy_distributionList__.projection_name string(200), AWScopy_resources__.resource_update_cycle_code string(200), AWScopy_projectionList__.resource_update_cycle_code string(200), AWScopy_distributionList__.resource_update_cycle_code string(200), AWScopy_resources__.resource_update_cycle_fr string(200), AWScopy_projectionList__.resource_update_cycle_fr string(200), AWScopy_distributionList__.resource_update_cycle_fr string(200), AWScopy_updateList__.resource_update_cycle string(200), AWScopy_updateList__.resource_update_cycle_code string(200), AWScopy_updateList__.resource_update_cycle_fr string(200), AWScopy_more_info_0_.link string(200), AWScopy_search_criteria_pycsw string(200), AWScopy__global_hashkey string(200), AWScopy__hash_pycsw string(200), AWScopy_csw_version string(200),
      AWScopy_csw_schema string(200), AWScopy_csw_typenames string(200), AWScopy_csw_filter string(200), AWScopy_result.file_id string(200), AWScopy_csw_search_criteria string(200), AWScopy_MD_Metadata.MD_Metadata string(200), AWScopy__OpenMapsFilter string(200), AWScopy_result.results string(200), AWScopy__list_name string(200), AWScopy_MD_Metadata.fileIdentifier.CharacterString string(200), AWScopy_MD_Metadata.path_windows string(200), AWScopy_MD_Metadata.path_extension string(200), AWScopy_path_windows string(200), AWScopy_path_extension string(200), urls_https__ string(200), urls_http__ string(200), urls_ftp__ string(200), length_issue string(200), _total_number number(20), _translation_problem string(200), _timestamp string(200)

Bookmark: XML CREATION AND WRITING
Note: Reading Config_YT
LOOKUP_TABLES_READER_14
    CSV_ENCODING = utf-8
    CSV_PATH = $(IN_CSV_LOOKUP_TABLES_DIR)
    FEATURE_TYPE = Config_YT
    PT = YT
    -> XML_PUBLISHER [CONFIG_FILE]
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER
    LOCAL_WRITER = $(LOCAL_WRITER)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    INSERT_FAILED -> text_line (writer TEXTLINE_2)
    UPDATE_PASSED -> text_line (writer TEXTLINE_1)
    UPDATE_FAILED -> text_line (writer TEXTLINE_2)
